(defun c:RunPurge ( / )
  ;(command "_.SCRIPT" "C:\\ProgramData\\Autodesk\\ApplicationPlugins\\SpNwDo.bundle\\Contents\\Scr\\RenameTbmBlock")
  (command "_.SCRIPT" "C:\\ProgramData\\Autodesk\\ApplicationPlugins\\SpNwDo.bundle\\Contents\\Scr\\Purge")
)
