(command "netload" "C:\\ProgramData\\Autodesk\\ApplicationPlugins\\SpNwDo.bundle\\Contents\\Plugin\\LokalisatieSeinen.dll")
	(command "netload" "C:\\ProgramData\\Autodesk\\ApplicationPlugins\\SpNwDo.bundle\\Contents\\Plugin\\PlotPdf.dll")
	(command "netload" "C:\\ProgramData\\Autodesk\\ApplicationPlugins\\SpNwDo.bundle\\Contents\\Plugin\\CmdTools.dll")
	(command "netload" "C:\\ProgramData\\Autodesk\\ApplicationPlugins\\SpNwDo.bundle\\Contents\\Plugin\\ImportNewAlstom.dll")
	(command "netload" "C:\\ProgramData\\Autodesk\\ApplicationPlugins\\SpNwDo.bundle\\Contents\\Plugin\\CreateVk.dll")

	(load "C:\\ProgramData\\Autodesk\\ApplicationPlugins\\SpNwDo.bundle\\Contents\\Lisp\\RunPurge.lsp")
	(load "C:\\ProgramData\\Autodesk\\ApplicationPlugins\\SpNwDo.bundle\\Contents\\Lisp\\RunScript.lsp")

;; voorbeeld pad
;;(command "netload" "C:\\ProgramData\\Autodesk\\ApplicationPlugins\\VvdkNwDo.bundle\\Contents\\Plugin\\.dll")
;;(load "C:\\ProgramData\\Autodesk\\ApplicationPlugins\\VvdkNwDo.bundle\\Contents\\AutoLisp\\.lsp")
